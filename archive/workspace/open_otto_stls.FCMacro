"""Layout Otto DIY's four original printable STL types for inspection."""
import FreeCAD as App, Mesh, os, traceback
from FreeCAD import Vector
ROOT=r'C:\Users\user\OneDrive\Documents\ChatGPT\simple_robot'
OUT=os.path.join(ROOT,'otto_freecad_reference')
os.makedirs(OUT,exist_ok=True)
try:
    doc=App.newDocument('Otto_Four_Servo_Print_Parts')
    src=os.path.join(ROOT,'otto_reference','3Dprint')
    for i,(name,file) in enumerate([
        ('Head','OttoDIY_head_V9.stl'),('Body','OttoDIY_body_V9.stl'),
        ('Leg_1','OttoDIY_Leg_V9.stl'),('Leg_2','OttoDIY_Leg_V9.stl'),
        ('Foot_1','OttoDIY_foot_V9.stl'),('Foot_2','OttoDIY_foot_V9.stl')]):
        mesh=Mesh.Mesh(os.path.join(src,file));b=mesh.BoundBox
        mesh.translate((i%3)*100-(b.XMin+b.XMax)/2,-(i//3)*100-(b.YMin+b.YMax)/2,-b.ZMin)
        obj=doc.addObject('Mesh::Feature',name);obj.Mesh=mesh;obj.Label=name.replace('_',' ')
        obj.addProperty('App::PropertyString','Source','Reference');obj.Source=file
        obj.ViewObject.ShapeColor=(0.28,0.7,0.27)
    doc.recompute();view=Gui.activeDocument().activeView()
    if hasattr(view,'setAnimationEnabled'):view.setAnimationEnabled(False)
    view.viewAxonometric();view.fitAll();Gui.updateGui()
    doc.saveAs(os.path.join(OUT,'Otto_Four_Servo_Print_Parts.FCStd'))
    view.saveImage(os.path.join(OUT,'otto_print_parts.png'),1200,1000,'White')
    with open(os.path.join(OUT,'stl_status.txt'),'w') as f:f.write('SUCCESS')
except Exception:
    with open(os.path.join(OUT,'stl_status.txt'),'w') as f:f.write(traceback.format_exc())
    raise
