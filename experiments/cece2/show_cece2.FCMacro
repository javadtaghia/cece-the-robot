"""Open a separate Cece 2 inspection assembly, preserving Cece's CAD files."""
from pathlib import Path
import shutil,tempfile
import FreeCAD as App,FreeCADGui as Gui
HERE=Path(__file__).resolve().parent
source=HERE.parent/'cece'/'no_led_mouth'/'Cece_No_LED_Mouth_Assembly.FCStd'
doc=App.openDocument(str(source))
doc.Label='Cece 2 - fast gait candidate'
colors={'Rounded_Head_Study':(.88,.92,.96),'Rear_Cover_Study':(.76,.85,.93),
 'Body':(.85,.89,.94),'Heart_Frame_V3':(.88,.30,.45),
 'Left_Arm':(.56,.72,.84),'Right_Arm':(.56,.72,.84),
 'Left_Leg':(.58,.71,.83),'Right_Leg':(.58,.71,.83),
 'Left_Foot':(.36,.52,.69),'Right_Foot':(.36,.52,.69),
 'HC_SR04_Left_Can':(.28,.68,.76),'HC_SR04_Right_Can':(.28,.68,.76),
 'OLED_Adafruit4741_Official_CAD':(.12,.18,.25),
 'Left_Washer':(.35,.43,.51),'Right_Washer':(.35,.43,.51),
 'Antenna':(.96,.7,.32),'Camera_Lens_Corridor_Provisional':(.08,.1,.12),
 'Charger_Tray':(.6,.73,.8),'Charger_Bezel':(.45,.57,.67)}
for obj in doc.Objects:
    obj.ViewObject.Visibility=obj.Name in colors
    if obj.Name in colors:
        obj.ViewObject.ShapeColor=colors[obj.Name]
        obj.ViewObject.Transparency=0
        try:obj.ViewObject.DisplayMode='Flat Lines'
        except Exception:pass
meta=doc.addObject('App::FeaturePython','Cece2_Profile')
meta.addProperty('App::PropertyString','Status').Status='Same geometry as Cece; separate fast gait candidate, not hardware validated'
meta.addProperty('App::PropertyString','PhaseTimes_ms').PhaseTimes_ms='140, 60, 200, 60, 100'
meta.addProperty('App::PropertyString','ServoLayout').ServoLayout='Four SG90: hip yaw + ankle roll per leg'
view=Gui.activeDocument().activeView()
view.viewFront();view.fitAll()
Gui.updateGui()
doc.recompute()
temporary=Path(tempfile.mkdtemp(prefix='cece2_view_'))
doc.saveAs(str(temporary/'Cece2_Assembly.FCStd'))
shutil.copy2(temporary/'Cece2_Assembly.FCStd',HERE/'Cece2_Assembly.FCStd')
view.saveImage(str(temporary/'Cece2_FreeCAD_Front.png'),1200,900,'White')
shutil.copy2(temporary/'Cece2_FreeCAD_Front.png',HERE/'Cece2_FreeCAD_Front.png')
